Attribute VB_Name = "Module1"
Sub CATMain()
    Dim oPartDocument As PartDocument
    Dim oPart As Part
    Dim oHybridBodies1 As HybridBodies
    Dim oHB1 As HybridBody
    Dim oHB2() As HybridBody
    Dim iPoche As Integer
    Dim kPoche As Integer
    Dim oExtrapol1() As HybridShapeExtrapol
    Dim nbExtrapol As Integer
    Dim oAssemble4() As HybridShapeAssemble
    nbExtrapol = 0
    
    Set oPartDocument = CATIA.ActiveDocument
    Set oPart = oPartDocument.Part
    Set oHybridBodies1 = oPart.HybridBodies
    Set oHB1 = oHybridBodies1.Add()
    oHB1.Name = "CONSTRUCTIONS CN"
    oPart.Update
    
    Dim oBody1 As Body
    Set oBody1 = oPart.Bodies.Item(1)

    Dim oFace1
    Set oFace1 = oPart.HybridBodies.Item("CONSTRUCTION MMS").HybridShapes.Item("surface piece")
    
    'Sélection de la face de référence
    Dim oSel1
    Dim InPutObjectType(0)
    Dim oFacePrincipale
    Dim oFacePrincipaleColor_R As Long, oFacePrincipaleColor_G As Long, oFacePrincipaleColor_B As Long
    CATIA.RefreshDisplay = False
    Set oSel1 = oPartDocument.Selection
    oSel1.Clear
    InPutObjectType(0) = "Face"
    Status = oSel1.SelectElement3(InPutObjectType, "Selectionner une face", False, CATMultiSelTriggWhenSelPerf, False)
    If (Status = "Cancel") Then Exit Sub
    Set oFacePrincipale = oSel1.Item2(1).Value
    oSel1.VisProperties.GetRealColor oFacePrincipaleColor_R, oFacePrincipaleColor_G, oFacePrincipaleColor_B
    
    'Mesure épaisseur de la face de référence
    Dim oPointOnSurface1 As HybridShapePointOnSurface
    Dim oDirection As HybridShapeDirection
    Dim faceR As Reference
    Dim oProjectTMP As HybridShapeProject
    Dim TheSPAWorkbench As SPAWorkbench
    Dim Measurable1 As Measurable
    Dim Measurable2 As Measurable
    Dim distance As Double
    
    Set oAssembleTmp = oPart.HybridShapeFactory.AddNewJoin(oSel1.Item2(1).Value, oSel1.Item2(1).Value)
    Set faceR = oPart.CreateReferenceFromObject(oAssembleTmp)
    Set oDirection = oPart.HybridShapeFactory.AddNewDirection(faceR)
    Set oPointOnSurface1 = oPart.HybridShapeFactory.AddNewPointOnSurface(faceR, oDirection, 0#)
    oHB1.AppendHybridShape oPointOnSurface1
    Set oProjectTMP = oPart.HybridShapeFactory.AddNewProject(oPointOnSurface1, oFace1)
    oProjectTMP.SolutionType = 0
    oProjectTMP.Normal = True
    oProjectTMP.SmoothingType = 0
    oHB1.AppendHybridShape oProjectTMP
    oPart.Update
    
    Set TheSPAWorkbench = CATIA.ActiveDocument.GetWorkbench("SPAWorkbench")
    Set Measurable1 = TheSPAWorkbench.GetMeasurable(oPointOnSurface1)
    Set Measurable2 = TheSPAWorkbench.GetMeasurable(oProjectTMP)
    distance = Measurable2.GetMinimumDistance(oPointOnSurface1)
    If distance = 0 Then
        MsgBox "La surface séléctionnée est à 0mm de la surface de référence"
    Exit Sub
    End If
    oHB1.Name = "Usinages Epaisseur " & Round(distance, 2)
    oSel1.Clear
    oSel1.Add oPointOnSurface1
    oSel1.Add oProjectTMP
    oSel1.Delete
    
    'Sélection des faces de la même couleur que la face de référence
    Dim iNbFaces As Integer
    oSel1.Clear
    oSel1.Add oBody1
    oPartDocument.Selection.Search ("Topology.CGMFace & Color='(" & oFacePrincipaleColor_R & "," & oFacePrincipaleColor_G & "," & oFacePrincipaleColor_B & ")',sel")
    Set oSel1 = oPartDocument.Selection
    iNbFaces = oSel1.Count2
    Dim oFace()
    ReDim oFace(iNbFaces)
    For J = 1 To iNbFaces
        Set oFace(J) = oSel1.Item2(J).Value
    Next J
    oPart.Update
    
    'Assemblage des faces sélectionnées connexes
    Dim oAssemble1() As HybridShapeAssemble
    Dim NbfacesAdded As Integer
    Dim NbFaceOri As Integer
    Dim nbkOK As Integer
    NbFaceOri = iNbFaces
    iPoche = 1
    For J = 1 To iNbFaces
        If Not oFace(J) Is Nothing Then
            ReDim Preserve oAssemble1(iPoche)
            ReDim Preserve oHB2(iPoche)
            Set oHB2(iPoche) = oHB1.HybridBodies.Add()
            oHB2(iPoche).Name = "Constructions Poche." & iPoche
            Set oAssemble1(iPoche) = oPart.HybridShapeFactory.AddNewJoin(oFace(J), oFace(J))
            oAssemble1(iPoche).SetConnex True
            oAssemble1(iPoche).SetTangencyContinuity False
            oAssemble1(iPoche).Name = "Surface_Poche." & iPoche
            oHB2(iPoche).AppendHybridShape oAssemble1(iPoche)
            If Not oFace(J) Is Nothing Then oAssemble1(iPoche).RemoveElement 2
            Set oFace(J) = Nothing
            iNbFaces = iNbFaces - 1
            NbfacesAdded = 1
            For i = J + 1 To NbFaceOri
                'If Not oFace(i) Is Nothing Then
                nbkOK = 0
                    For k = 2 To NbFaceOri
                        If Not oFace(k) Is Nothing Then
                            oAssemble1(iPoche).AddElement oFace(k)
                            NbfacesAdded = NbfacesAdded + 1
                            On Error Resume Next
                            oPart.Update
                            If (Err.Number <> 0) Then
                                oAssemble1(iPoche).RemoveElement NbfacesAdded
                                NbfacesAdded = NbfacesAdded - 1
                                Err.Clear
                            Else
                                iNbFaces = iNbFaces - 1
                                nbkOK = nbkOK + 1
                                Set oFace(k) = Nothing
                            End If
                            On Error GoTo 0
                        End If
                        If iNbFaces = 0 Then Exit For
                        If k >= NbFaceOri Then Exit For
                    Next k
                    If nbkOK = 0 Then Exit For
                'End If
                
                If iNbFaces = 0 Then Exit For
            Next i
            If iNbFaces = 0 Then Exit For
            iPoche = iPoche + 1
            NbfacesAdded = 0
        End If
    Next J
    'Assemblage des faces sélectionnées connexes à la face de référence
    For kPoche = 1 To iPoche
        'Extraction des frontières
        Dim oBoundary1 As HybridShapeBoundary
        'oPart.Update
        Set oBoundary1 = oPart.HybridShapeFactory.AddNewBoundaryOfSurface(oPart.CreateReferenceFromObject(oAssemble1(kPoche)))
        oHB2(kPoche).AppendHybridShape oBoundary1
        oPart.Update
        
        'Eclatement des frontières pour déterminer quels sont les portions ouvertes et fermées
        Dim mySel
        Dim oCrvRef
        Dim miLongitud
        Dim strTmp
        Dim Texto As String
        Dim oRefCurv()
        Dim oCurv() As HybridShapeCurveExplicit
        Dim oExtract1() As HybridShapeExtract
        Dim n As Integer
        Dim nbCurv As Integer
        Dim oPointOnCurve1() As HybridShapePointOnCurve
        Dim oPointOnCurve2() As HybridShapePointOnCurve
        Dim oPlaneNormal1() As HybridShapePlaneNormal
        Dim oPlaneTangent1() As HybridShapePlaneTangent
        Dim oDirection1() As HybridShapeDirection
        Dim oLinePtDir1() As HybridShapeLinePtDir
        Dim oPlaneAngle1() As HybridShapePlaneAngle
        Dim oDirection2() As HybridShapeDirection
        Dim oLinePtDir2() As HybridShapeLinePtDir
        Dim oIntersection1() As HybridShapeIntersection
        
        oSel1.Clear
        oSel1.Add oBoundary1
        oSel1.Search "Topology.CGMEdge,sel"
        nbCurv = oSel1.Count
        ReDim oRefCurv(nbCurv)
        ReDim oCurv(nbCurv)
        ReDim oPointOnCurve1(nbCurv)
        ReDim oPlaneNormal1(nbCurv)
        ReDim oPlaneTangent1(nbCurv)
        ReDim oDirection1(nbCurv)
        ReDim oLinePtDir1(nbCurv)
        ReDim oPointOnCurve2(nbCurv)
        ReDim oPlaneAngle1(nbCurv)
        ReDim oDirection2(nbCurv)
        ReDim oLinePtDir2(nbCurv)
        ReDim oIntersection1(nbCurv)
        ReDim oExtract1(nbCurv)
        For n = 1 To nbCurv
            Set mySel = oSel1.Item(n)
            Set oCrvRef = mySel.Reference
            miLongitud = Len(mySel.Reference.Name)
            strTmp = Right(mySel.Reference.Name, miLongitud - 21)
            miLongitud = Len(strTmp)
            Texto = Left(strTmp, miLongitud - 1)
            Set oRefCurv(n) = oPart.CreateReferenceFromBRepName(Texto, mySel.Value)
            Set oCurv(n) = oPart.HybridShapeFactory.AddNewCurveDatum(oRefCurv(n))
            oCurv(n).Compute
            Set oRefCurv(n) = oPart.CreateReferenceFromObject(oCurv(n))
        Next n
        For n = 1 To nbCurv
            
            Set oExtract1(n) = oPart.HybridShapeFactory.AddNewExtract(oRefCurv(n))
            oHB2(kPoche).AppendHybridShape oExtract1(n)

            'Détermination du point millieu de chaques courbes
            Set oPointOnCurve1(n) = oPart.HybridShapeFactory.AddNewPointOnCurveFromPercent(oCurv(n), 0.5, False)
            oPointOnCurve1(n).Compute
            oHB2(kPoche).AppendHybridShape oPointOnCurve1(n)
            
            'Création du plan normal, au millieu de chaques courbes
            Set oPlaneNormal1(n) = oPart.HybridShapeFactory.AddNewPlaneNormal(oCurv(n), oPointOnCurve1(n))
            oHB2(kPoche).AppendHybridShape oPlaneNormal1(n)
            
            'Création du plan tangent, au millieu de chaques courbes
            Set oPlaneTangent1(n) = oPart.HybridShapeFactory.AddNewPlaneTangent(oAssemble1(kPoche), oPointOnCurve1(n))
            oHB2(kPoche).AppendHybridShape oPlaneTangent1(n)
            
            'Création de la droite de normale à la surface assemblé au milieu de chaque courbe
            Set oDirection1(n) = oPart.HybridShapeFactory.AddNewDirection(oPlaneTangent1(n))
            Set oLinePtDir1(n) = oPart.HybridShapeFactory.AddNewLinePtDir(oPointOnCurve1(n), oDirection1(n), -0, 0.1, True)
            oHB2(kPoche).AppendHybridShape oLinePtDir1(n)
            
            'Détermination du sommet de chaque droite
            Set oPointOnCurve2(n) = oPart.HybridShapeFactory.AddNewPointOnCurveFromPercent(oLinePtDir1(n), 0, False)
            oPointOnCurve2(n).Compute
            oHB2(kPoche).AppendHybridShape oPointOnCurve2(n)
            
            'Création du plan Tangent à chaques courbes
            Set oPlaneAngle1(n) = oPart.HybridShapeFactory.AddNewPlaneAngle(oPlaneNormal1(n), oLinePtDir1(n), 90#, False)
            oHB2(kPoche).AppendHybridShape oPlaneAngle1(n)
            
            'Tir
            Set oDirection2(n) = oPart.HybridShapeFactory.AddNewDirection(oPlaneAngle1(n))
            Set oLinePtDir2(n) = oPart.HybridShapeFactory.AddNewLinePtDir(oPointOnCurve2(n), oDirection2(n), -1, 1, True)
            oHB2(kPoche).AppendHybridShape oLinePtDir2(n)
            
            'Test impact
            Set oIntersection1(n) = oPart.HybridShapeFactory.AddNewIntersection(oLinePtDir2(n), oPart.CreateReferenceFromObject(oBody1))
            oHB2(kPoche).AppendHybridShape oIntersection1(n)
            On Error Resume Next
            oPart.Update
            If (Err.Number <> 0) Then
                Err.Clear
                oExtract1(n).Name = oExtract1(n).Name & "_O"
            Else
                oExtract1(n).Name = oExtract1(n).Name & "_F"
            End If
            On Error GoTo 0
            'Nétoyage
            oSel1.Clear
            oSel1.Add oPointOnCurve1(n)
            oSel1.Add oPlaneNormal1(n)
            oSel1.Add oPlaneTangent1(n)
            oSel1.Add oDirection1(n)
            oSel1.Add oLinePtDir1(n)
            oSel1.Add oPointOnCurve2(n)
            oSel1.Add oPlaneAngle1(n)
            oSel1.Add oDirection2(n)
            oSel1.Add oLinePtDir2(n)
            oSel1.Add oIntersection1(n)
            oSel1.Delete
        Next n
        
        'Assemblage des courbes Fermée/ouverte et connexe
        Dim oAssemble2() As HybridShapeAssemble
        Dim iAss As Integer
        iAss = 1
        ReDim oAssemble2(iAss)
        Set oAssemble2(iAss) = oPart.HybridShapeFactory.AddNewJoin(oExtract1(1), oExtract1(1))
        oAssemble2(iAss).SetConnex True
        oAssemble2(iAss).SetTangencyContinuity False
        oHB2(kPoche).AppendHybridShape oAssemble2(iAss)
        oAssemble2(iAss).RemoveElement 2
        If Right(oExtract1(1).Name, 1) = "O" Then
            oAssemble2(iAss).Name = oAssemble2(iAss).Name & "_O"
        ElseIf Right(oExtract1(1).Name, 1) = "F" Then
            oAssemble2(iAss).Name = oAssemble2(iAss).Name & "_F"
        End If
        If nbCurv > 1 Then
            For n = 2 To nbCurv
                oAssemble2(iAss).AddElement oExtract1(n)
                On Error Resume Next
                oPart.Update
                If (Err.Number <> 0) Or Right(oExtract1(n).Name, 1) <> Right(oAssemble2(iAss).Name, 1) Then
                    oAssemble2(iAss).RemoveElement oAssemble2(iAss).GetElementsSize
                    Err.Clear
                    iAss = iAss + 1
                    ReDim Preserve oAssemble2(iAss)
                    Set oAssemble2(iAss) = oPart.HybridShapeFactory.AddNewJoin(oExtract1(n), oExtract1(n))
                    oAssemble2(iAss).SetConnex True
                    oAssemble2(iAss).SetTangencyContinuity False
                    oHB2(kPoche).AppendHybridShape oAssemble2(iAss)
                    oAssemble2(iAss).RemoveElement 2
                    If Right(oExtract1(n).Name, 1) = "O" Then
                        oAssemble2(iAss).Name = oAssemble2(iAss).Name & "_O"
                    ElseIf Right(oExtract1(n).Name, 1) = "F" Then
                        oAssemble2(iAss).Name = oAssemble2(iAss).Name & "_F"
                    End If
                End If
                On Error GoTo 0
            Next n
        End If
        
        Dim oAssemble3() As HybridShapeAssemble
        Dim iContour As Integer
        iContour = 1
        J = 0
        For i = 1 To iAss
            If i <> J Then
                ReDim Preserve oAssemble3(iContour)
                Set oAssemble3(iContour) = oPart.HybridShapeFactory.AddNewJoin(oAssemble2(i), oAssemble2(i))
                oAssemble3(iContour).SetConnex True
                oAssemble3(iContour).SetTangencyContinuity False
                oHB1.AppendHybridShape oAssemble3(iContour)
                oAssemble3(iContour).RemoveElement 2
                If Right(oAssemble2(i).Name, 1) = "O" Then
                    oAssemble3(iContour).Name = "Poche." & kPoche & "_Contour." & iContour & "_O"
                ElseIf Right(oAssemble2(i).Name, 1) = "F" Then
                    oAssemble3(iContour).Name = "Poche." & kPoche & "_Contour." & iContour & "_F"
                End If
                'oPart.Update '''
                If J = 0 Then
                    For J = i + 1 To iAss
                        On Error Resume Next
                        oAssemble3(iContour).AddElement oAssemble2(J)
                        oPart.Update
                        If (Err.Number <> 0) Or Right(oAssemble2(J).Name, 1) <> Right(oAssemble3(iContour).Name, 1) Then
                            oAssemble3(iContour).RemoveElement oAssemble3(iContour).GetElementsSize
                            Err.Clear
                            On Error GoTo 0
                        Else
                        On Error GoTo 0
                        'oPart.Update '''
                        Exit For
                        End If
                    Next J
                End If
                oPart.Update
                oSel1.Clear
                oSel1.Add oAssemble3(iContour)
                oSel1.VisProperties.SetRealColor 250, 0, 0, 1
                oSel1.VisProperties.SetRealWidth 3, 0
                If Right(oAssemble3(iContour).Name, 1) = "O" Then
                    oSel1.VisProperties.SetRealLineType 2, 0
                    'Extrapolation de chaque surfaces
                    nbExtrapol = nbExtrapol + 1
                    ReDim Preserve oExtrapol1(nbExtrapol)
                    Set oExtrapol1(nbExtrapol) = oPart.HybridShapeFactory.AddNewExtrapolLength(oAssemble3(iContour), oAssemble1(kPoche), 2#)
                    oExtrapol1(nbExtrapol).ContinuityType = 1
                    oExtrapol1(nbExtrapol).BorderType = 1
                    oExtrapol1(nbExtrapol).LimitType = 0
                    oExtrapol1(nbExtrapol).SetAssemble False
                    oExtrapol1(nbExtrapol).PropagationMode = 0
                    oExtrapol1(nbExtrapol).ExtendEdgesMode = False
                    oExtrapol1(nbExtrapol).ConstantLengthMode = False
                    oHB2(kPoche).AppendHybridShape oExtrapol1(nbExtrapol)
                    'oPart.Update
                End If
            End If
            If i >= iAss Then Exit For
            iContour = iContour + 1
        Next i
        ReDim Preserve oAssemble4(kPoche)
        Set oAssemble4(kPoche) = oPart.HybridShapeFactory.AddNewJoin(oAssemble1(kPoche), oAssemble1(kPoche))
        oAssemble4(kPoche).SetConnex True
        oAssemble4(kPoche).SetTangencyContinuity False
        oHB1.AppendHybridShape oAssemble4(kPoche)
        oAssemble4(kPoche).RemoveElement 2
        oAssemble4(kPoche).Name = "Surface_Poche." & kPoche
        For i = 1 To nbExtrapol
            oAssemble4(kPoche).AddElement oExtrapol1(i)
        Next i
        nbExtrapol = 0
        
        'oPart.Update
    Next kPoche
    oPart.Update
    CATIA.StartCommand "Réduire tout"
End Sub

Attribute VB_Name = "Module2"
Sub CATMain()

Dim documents1 As Documents
Set documents1 = CATIA.Documents

Dim partDocument1 As PartDocument
Set partDocument1 = documents1.Item("AG_UPR_MINUMAC_SMSC531410101A1P02_DEBIT_corrige.CATPart")

Dim part1 As Part
Set part1 = partDocument1.Part

Dim hybridShapeFactory1 As HybridShapeFactory
Set hybridShapeFactory1 = part1.HybridShapeFactory

Dim hybridBodies1 As HybridBodies
Set hybridBodies1 = part1.HybridBodies

Dim hybridBody1 As HybridBody
Set hybridBody1 = hybridBodies1.Item("CONSTRUCTION MMS")

Dim hybridShapes1 As HybridShapes
Set hybridShapes1 = hybridBody1.HybridShapes

Dim hybridShapeHealing1 As HybridShapeHealing
Set hybridShapeHealing1 = hybridShapes1.Item("surface brut")

Dim reference1 As Reference
Set reference1 = part1.CreateReferenceFromObject(hybridShapeHealing1)

Dim hybridBody2 As HybridBody
Set hybridBody2 = hybridBodies1.Item("CONSTRUCTION CN")

Dim hybridBodies2 As HybridBodies
Set hybridBodies2 = hybridBody2.HybridBodies

Dim hybridBody3 As HybridBody
Set hybridBody3 = hybridBodies2.Item("Construction_parcours_mesure_surface")

Dim hybridShapes2 As HybridShapes
Set hybridShapes2 = hybridBody3.HybridShapes

Dim hybridShapeAssemble1 As HybridShapeAssemble
Set hybridShapeAssemble1 = hybridShapes2.Item("Assembler.21")

Dim reference2 As Reference
Set reference2 = part1.CreateReferenceFromObject(hybridShapeAssemble1)

Dim hybridShapeSplit1 As HybridShapeSplit
Set hybridShapeSplit1 = hybridShapeFactory1.AddNewHybridSplit(part1.CreateReferenceFromObject(hybridShapeHealing1), part1.CreateReferenceFromObject(hybridShapeAssemble1), 1)
hybridShapeFactory1.GSMVisibility reference1, 0
hybridBody3.AppendHybridShape hybridShapeSplit1


part1.Update

part1.Update

End Sub
